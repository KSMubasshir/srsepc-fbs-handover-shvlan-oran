-- **************************************************************
-- E2SM-MOB
-- Mobility (handover) reporting service model
--
-- Periodic reports of an eNB's handover counters, per-UE handover
-- state and last measurement report, and a log of handover and
-- RRC re-establishment events.
--
-- Measurement values are TS 36.133 report mappings:
--   RSRP 0..97 ~ (value - 140) dBm, RSRQ 0..34 ~ (value / 2 - 20) dB.
-- **************************************************************

E2SM-MOB-IEs {
iso(1) identified-organization(3) dod(6) internet(1) private(4) enterprise(1) 53148 e2(1) version1 (1) e2sm(2) e2sm-MOB-IEs (102)}

DEFINITIONS AUTOMATIC TAGS ::=

BEGIN

maxOfCells INTEGER ::= 16
maxOfUes INTEGER ::= 256
maxOfNeighCells INTEGER ::= 8
maxOfEvents INTEGER ::= 64

Counter ::= INTEGER (0..4294967295)
TimeSec ::= INTEGER (0..4294967295)
TimeMs ::= INTEGER (0..999)
C-RNTI ::= INTEGER (0..65535)
PCI ::= INTEGER (0..503)
ECI ::= INTEGER (0..268435455)
RSRP ::= INTEGER (0..97)
RSRQ ::= INTEGER (0..34)

-- **************************************************************
-- RAN Function Description
-- **************************************************************

RANfunction-Name ::= SEQUENCE {
    ranFunction-ShortName   PrintableString(SIZE(1..150,...)),
    ranFunction-E2SM-OID    PrintableString(SIZE(1..1000,...)),
    ranFunction-Description PrintableString(SIZE(1..150,...)),
    ranFunction-Instance    INTEGER OPTIONAL,
    ...
}

RANfunction-Description ::= SEQUENCE {
    ranFunction-Name RANfunction-Name,
    ...
}

-- **************************************************************
-- Event Trigger and Action Definitions
-- **************************************************************

E2SM-Mob-EventTriggerDefinition ::= CHOICE {
    periodDefinition E2SM-Mob-EventTriggerDefinition-Period,
    ...
}

E2SM-Mob-EventTriggerDefinition-Period ::= SEQUENCE {
    period INTEGER (10..10240),
    ...
}

E2SM-Mob-ActionType ::= ENUMERATED {
    mobilityReport,
    ...
}

E2SM-Mob-ActionDefinition ::= SEQUENCE {
    actionType E2SM-Mob-ActionType,
    ...
}

-- **************************************************************
-- Report contents
-- **************************************************************

CellInfo ::= SEQUENCE {
    cellId   INTEGER (0..255),
    pci      PCI,
    dlEarfcn INTEGER (0..262143),
    ...
}

HoCounters ::= SEQUENCE {
    -- S1 handover, this eNB as source
    s1OutAttempt     Counter,
    s1OutPrepSuccess Counter,
    s1OutPrepFailure Counter,
    s1OutSuccess     Counter,
    s1OutFailure     Counter,
    -- S1 handover, this eNB as target
    s1InAttempt      Counter,
    s1InPrepSuccess  Counter,
    s1InPrepFailure  Counter,
    s1InSuccess      Counter,
    s1InFailure      Counter,
    -- intra-eNB handover
    intraAttempt     Counter,
    intraSuccess     Counter,
    intraFailure     Counter,
    -- RRC connection re-establishment
    reestAttempt     Counter,
    reestSuccess     Counter,
    reestReject      Counter,
    measReports      Counter,
    ...
}

MeasResult ::= SEQUENCE {
    pci  PCI,
    rsrp RSRP OPTIONAL,
    rsrq RSRQ OPTIONAL,
    ...
}

UeMeasReport ::= SEQUENCE {
    ageMs      Counter,
    nReports   Counter,
    measId     INTEGER (1..32),
    serving    MeasResult,
    neighbours SEQUENCE (SIZE(0..maxOfNeighCells)) OF MeasResult,
    ...
}

RrcState ::= ENUMERATED {
    idle,
    waitConSetupComplete,
    waitConReestComplete,
    waitSecurityModeComplete,
    waitUeCapInfo,
    waitConReconfComplete,
    reestablishmentComplete,
    registered,
    releaseRequest,
    ...
}

MobilityState ::= ENUMERATED {
    idle,
    s1SourcePreparation,
    s1SourceExecution,
    s1TargetPreparation,
    s1TargetExecution,
    intraEnb,
    ...
}

UeMobilityStatus ::= SEQUENCE {
    rnti           C-RNTI,
    rrcState       RrcState,
    mobilityState  MobilityState,
    servingPci     PCI OPTIONAL,
    lastMeasReport UeMeasReport OPTIONAL,
    ...
}

HoEventType ::= ENUMERATED {
    s1OutPrepStart,
    s1OutPrepSuccess,
    s1OutPrepFailure,
    s1OutSuccess,
    s1OutFailure,
    s1InRequest,
    s1InPrepSuccess,
    s1InPrepFailure,
    s1InSuccess,
    s1InFailure,
    intraStart,
    intraSuccess,
    intraFailure,
    reestRequest,
    reestSuccess,
    reestReject,
    ...
}

ReestCause ::= ENUMERATED {
    reconfigurationFailure,
    handoverFailure,
    otherFailure,
    ...
}

HoEvent ::= SEQUENCE {
    seq          Counter,
    timestampSec TimeSec,
    timestampMs  TimeMs,
    eventType    HoEventType,
    rnti         C-RNTI OPTIONAL,
    sourcePci    PCI OPTIONAL,
    targetPci    PCI OPTIONAL,
    targetEci    ECI OPTIONAL,
    -- at the handover decision (start events)
    servingRsrp  RSRP OPTIONAL,
    targetRsrp   RSRP OPTIONAL,
    -- outcome events: time since the handover started
    durationMs   Counter OPTIONAL,
    reestCause   ReestCause OPTIONAL,
    ...
}

MobilityReport ::= SEQUENCE {
    cellList    SEQUENCE (SIZE(0..maxOfCells)) OF CellInfo,
    counters    HoCounters,
    ueList      SEQUENCE (SIZE(0..maxOfUes)) OF UeMobilityStatus,
    -- events since the previous report of this subscription, oldest first
    eventList   SEQUENCE (SIZE(0..maxOfEvents)) OF HoEvent,
    -- events that occurred since the previous report but were dropped
    -- from the eNB's event log before they could be reported
    eventsLost  Counter,
    ...
}

-- **************************************************************
-- Indication Header and Message
-- **************************************************************

E2SM-Mob-IndicationHeader ::= SEQUENCE {
    timestampSec TimeSec,
    timestampMs  TimeMs,
    enbId        INTEGER (0..1048575),
    ...
}

E2SM-Mob-IndicationMessage ::= CHOICE {
    mobilityReport MobilityReport,
    ...
}

END
